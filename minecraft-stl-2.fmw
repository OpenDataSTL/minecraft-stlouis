FME workspace minecraft-stl-2.fmw

Parameters:
- DestDataset_MINECRAFT = C:\minecraft-stl\worlds   # Destination Minecraft Folder
- SourceDataset_SHAPE = C:\minecraft-stl\Soil_Survey.shp   # Source Esri Shape File(s)
- SourceDataset_ARCVIEWGRID = C:\minecraft-stl\dem   # Source Esri ArcGIS Binary Grid (AIG) Folder

Readers:
- SHAPE_1: SHAPE from $(SourceDataset_SHAPE) in LL-WGS84
- ARCVIEWGRID_1: ARCVIEWGRID from $(SourceDataset_ARCVIEWGRID) in MO83-EF

Writers:
- MINECRAFT_1: MINECRAFT to $(DestDataset_MINECRAFT)

Soil_Survey (reader SHAPE_1)
    attributes: PRIMFML number(20,0), STSSAID char(20), SHAPE_len number(31,15), MUSYM char(20), MUNAME char(20), SSAID number(20,0), MLRA number(20,0), MUKIND char(20), MUACRES number(20,0), MUID char(20)
    -> Reprojector
Reprojector
    RASTER_CELL_SIZE = Preserve Cells
    INTERPOLATION_TYPE_NAME = Nearest Neighbor
    DEST = MO83-EF
    SOURCE = Read from feature
    REPROJECTED -> TestFilter
Note: Data Flow
TestFilter
    TEST_LIST:
      BOOL_OP,OR,COMPOSITE_TEST,<Unused>,TEST_CLAUSE,"TEST @Value(MUNAME) CONTAINS CHERTY
      TEST @Value(MUNAME) CONTAINS SAND",Sand,BOOL_OP,OR,COMPOSITE_TEST,<Unused>,TEST_CLAUSE,"TEST @Value(MUNAME) CONTAINS ROCK
      TEST @Value(MUNAME) CONTAINS PITS",Stone,BOOL_OP,OR,COMPOSITE_TEST,<Unused>,TEST_CLAUSE,"TEST @Value(MUNAME) CONTAINS CLAY",Clay,BOOL_OP,OR,COMPOSITE_TEST,<Unused>,TEST_CLAUSE,"TEST @Value(MUNAME) CONTAINS WATER",Water
    DEFAULT_VALUE = <UNFILTERED>
    Sand -> MinecraftStylerSand
    Stone -> MinecraftStylerStone
    <UNFILTERED> -> MinecraftStylerDirt
    <UNFILTERED> -> MinecraftStylerGrass
    Water -> MinecraftStylerWater
    Clay -> MinecraftStylerClay
MinecraftStylerWater
    MINECRAFTBLOCK = 009
    VERTICALOFFSET = 0
    Styled -> MinecraftRasterizer [input 1]
MinecraftStylerSand
    MINECRAFTBLOCK = 012_00
    VERTICALOFFSET = 0
    Styled -> MinecraftRasterizer [input 1]
MinecraftStylerStone
    MINECRAFTBLOCK = 001_00
    VERTICALOFFSET = 0
    Styled -> MinecraftRasterizer [input 1]
MinecraftStylerClay
    MINECRAFTBLOCK = 159_07
    VERTICALOFFSET = 0
    Styled -> MinecraftRasterizer [input 1]
MinecraftStylerDirt
    MINECRAFTBLOCK = 003_00
    VERTICALOFFSET = 0
    Styled -> MinecraftRasterizer [input 1]
MinecraftStylerGrass
    MINECRAFTBLOCK = 031_01
    VERTICALOFFSET = 1
    Styled -> MinecraftRasterizer [input 1]
ARCVIEWGRID (reader ARCVIEWGRID_1)
    attributes: 
    -> Scaler_2
Scaler_2
    RASTER_SCALING = Extents
    YSCALE = 1
    XSCALE = 1
    TEXT_LOC_ONLY = Location and Size
    SCALE_ORIGIN = 0,0
    ZSCALE = 192/168
    SCALED -> MinecraftRasterizer [input 2]
MinecraftRasterizer
    _VERTICAL_OFFSET = @Value(_vertical_offset)
    BLOCKID = @Value(blockID)
    MINECRAFTRASTERIZER = 50
    BLOCKDATA = @Value(blockData)
    MinecraftPointCloud -> Scaler
Scaler
    RASTER_SCALING = Extents
    YSCALE = .02
    XSCALE = .02
    TEXT_LOC_ONLY = Location and Size
    SCALE_ORIGIN = 0,0
    ZSCALE = 1
    SCALED -> world3 (writer MINECRAFT_1)
world3 (writer MINECRAFT_1)

FME custom transformer MinecraftRasterizer

Parameters:
- MINECRAFTRASTERIZER = 1   # Cell size
- BLOCKID = @Value(blockID)   # blockID
- BLOCKDATA = @Value(blockData)   # blockData
- _VERTICAL_OFFSET = @Value(_vertical_offset)   # Vertical Offset

VectorInput (input)
    -> 3DForcer
    -> 3DForcer_2
    -> 3DForcer_3
Note: Make three bands - z, blockID, blockData. / PointCloudCombiner needs the first numeric band to be Z
RasterExpressionEvaluator
    MODE = Two Rasters
    EXPRESSION_LIST = INTERPRETATION_LIST "UINT16;UINT16;UINT16" EXPRESSION_LIST "0;A[0];B[0]"
    RESULT -> RasterExpressionEvaluator_2 [input 1]
Note: Add offset band
RasterExpressionEvaluator_2
    MODE = Two Rasters
    EXPRESSION_LIST = INTERPRETATION_LIST "UINT16;UINT16;UINT16;INT8" EXPRESSION_LIST "A[0];A[1];A[2];B[0]"
    RESULT -> RasterSelector
DEM (input)
    -> PointCloudOnRasterComponentSetter [input 2]
PointCloudFilter
    FILTER_TABLE = EXPRESSION_LIST @Component(blockID)==6 ; @Component(blockID)==37||@Component(blockID)==38 ; @Component(blockID)==31||@Component(blockID)==39||@Component(blockID)==40||@Component(blockID)==175 FILTER_ATTRIBUTE __pc_internal_filter_attribute__ FILTER_ATTRIBUTE_VALUES_LIST Trees ; Flowers ; OtherVegetation
    OUTPUT_UNFILTERED_POINTS = Yes
    <UNFILTERED> -> PointCloudCombiner_2
    Trees -> PointCloudFilter_2
    OtherVegetation -> PointCloudCombiner_2
    Trees -> MinecraftStyler_2
    OtherVegetation -> MinecraftStyler_2
    Flowers -> PointCloudCombiner_2
    Flowers -> MinecraftStyler_2
Note: All plants should grow / on grass or dirt
MinecraftStyler_2
    MINECRAFTBLOCK = 002
    VERTICALOFFSET = 0
    Styled -> PointCloudCombiner_2
Note: Randomly thin point cloud so that trees have some space between them
PointCloudFilter_2
    FILTER_TABLE = EXPRESSION_LIST @floor((@Component(x)*@Component(y)/1000-@floor(@Component(x)*@Component(y)/1000))*10)==1 FILTER_ATTRIBUTE __pc_internal_filter_attribute__ FILTER_ATTRIBUTE_VALUES_LIST EveryTenthPoint
    OUTPUT_UNFILTERED_POINTS = Yes
    EveryTenthPoint -> PointCloudCombiner_2
    <UNFILTERED> -> PointCloudExpressionEvaluator
Note: Where there is no tree, plant a random flower
PointCloudExpressionEvaluator
    EXPRESSION_TABLE = blockID Preserve if(@floor((@Component(x)*@Component(y)/1000-@floor(@Component(x)*@Component(y)/1000))*10)==5,37,38) blockData Preserve @floor((@Component(x)*@Component(y)/1000-@floor(@Component(x)*@Component(y)/1000))*9)
    RESULT -> PointCloudCombiner_2
Note: Make a single point cloud from all the parts
PointCloudCombiner_2
    ACCUM_ATTRS_NAME = Yes
    SPACING = $(MINECRAFTRASTERIZER)
    EXTRACT_RASTER_NODATA_NAME = No
    -> PointCloudPropertyExtractor
PointCloudPropertyExtractor
    POINT_COMPONENTS = x    y    z   MINMAX
    CALCULATE_EXTENTS_DISPLAY = No
    -> PointCloudExpressionEvaluator_4
Note: Scale, offset to higher ground, / and apply vertical offset where necessary
PointCloudExpressionEvaluator_4
    EXPRESSION_TABLE = z Auto 50.0/@Value(_z_max)*@Component(z)+50+@Component(vertical_offset)+50
    RESULT -> MinecraftPointCloud (output)
MinecraftPointCloud (output)

Bookmark: Rasterize by blockID
3DForcer
    ZVALATTR = @Value(blockID)
    -> NumericRasterizer
NumericRasterizer
    INTERPRETATION_TYPE = Int32
    Y_CELL_SIZE = $(MINECRAFTRASTERIZER)
    BACKGROUND_VALUE = -32767
    FILL_WITH_NODATA = Yes
    SPECIFY_GROUND_EXTENTS = Use input data ground extents
    TOLERANCE = 1
    ANTI_ALIASING = No
    ROWCOL_OR_CELLSIZE = CellSize
    X_CELL_SIZE = $(MINECRAFTRASTERIZER)
    RASTER -> RasterExpressionEvaluator [input 1]

Bookmark: Rasterize by blockData
3DForcer_2
    ZVALATTR = @Value(blockData)
    -> NumericRasterizer_2
NumericRasterizer_2
    INTERPRETATION_TYPE = Int32
    Y_CELL_SIZE = $(MINECRAFTRASTERIZER)
    BACKGROUND_VALUE = -32767
    FILL_WITH_NODATA = Yes
    SPECIFY_GROUND_EXTENTS = Use input data ground extents
    TOLERANCE = 1
    ANTI_ALIASING = No
    ROWCOL_OR_CELLSIZE = CellSize
    X_CELL_SIZE = $(MINECRAFTRASTERIZER)
    RASTER -> RasterExpressionEvaluator [input 2]

Bookmark: Rasterize by vertical offset
3DForcer_3
    ZVALATTR = @Value(_vertical_offset)
    -> NumericRasterizer_3
NumericRasterizer_3
    INTERPRETATION_TYPE = Int8
    Y_CELL_SIZE = $(MINECRAFTRASTERIZER)
    BACKGROUND_VALUE = 0
    FILL_WITH_NODATA = Yes
    SPECIFY_GROUND_EXTENTS = Use input data ground extents
    TOLERANCE = 1
    ANTI_ALIASING = No
    ROWCOL_OR_CELLSIZE = CellSize
    X_CELL_SIZE = $(MINECRAFTRASTERIZER)
    RASTER -> RasterExpressionEvaluator_2 [input 2]

Bookmark: Name the bands so that hey will turn into point cloud component names, and make a point cloud
RasterSelector
    BAND_LIST = 1:ALL
    SELECTION_MODE = Band and Palette List
    -> RasterBandNameSetter
RasterBandNameSetter
    INPUT_TYPE = Single Name
    BAND_NAME = blockID
    -> RasterSelector_2
RasterSelector_2
    BAND_LIST = 2:ALL
    SELECTION_MODE = Band and Palette List
    -> RasterBandNameSetter_2
RasterBandNameSetter_2
    INPUT_TYPE = Single Name
    BAND_NAME = blockData
    -> RasterSelector_4
RasterSelector_4
    BAND_LIST = 3:ALL
    SELECTION_MODE = Band and Palette List
    -> RasterBandNameSetter_3
RasterBandNameSetter_3
    INPUT_TYPE = Single Name
    BAND_NAME = vertical_offset
    -> RasterSelector_3
RasterSelector_3
    BAND_LIST = ALL ALL
    SELECTION_MODE = Band and Palette List
    -> PointCloudCombiner
PointCloudCombiner
    ACCUM_ATTRS_NAME = Yes
    SPACING = $(MINECRAFTRASTERIZER)
    EXTRACT_RASTER_NODATA_NAME = No
    -> PointCloudOnRasterComponentSetter [input 1]
Note: Transfer z from DEM to point cloud
PointCloudOnRasterComponentSetter
    COMPONENT_MAPPING = 0|z|
    EXTRACT_NODATA = No
    COMPONENT_SPECIFICATION = Custom
    DEFAULT_VALUES_OVERWRITE_DATA = No
    INTERPOLATION = Average 16
    PointCloud -> PointCloudFilter

FME custom transformer MinecraftStyler_2
Sets Minecraft blockID and blockData

Parameters:
- MINECRAFTBLOCK = 001_00
- VERTICALOFFSET = 0   # Vertical Offset

Input (input)
    -> ParameterFetcher_3
ParameterFetcher_3
    ATTR_LIST = _vertical_offset {$(VERTICALOFFSET)}
    -> GeometryFilter
GeometryFilter
    BREAK_AGG = No
    GEOM_PORT_NAMES = Pointcloud
    <UNFILTERED> -> AttributeCreator_2
    POINTCLOUD -> PointCloudComponentRemover
PointCloudComponentRemover
    COMPONENTS_TO_REMOVE = blockID,blockData,vertical_offset
    -> ParameterFetcher
ParameterFetcher
    ATTR_LIST = MinecraftBlock {$(MINECRAFTBLOCK)}
    -> AttributeSplitter_2
AttributeSplitter_2
    ATTR_NAME = MinecraftBlock
    DELIMITER = _
    TRIM_OPTION = Both
    LIST_NAME = _list
    DROP_EMPTY_PARTS = No
    -> AttributeCreator_3
AttributeCreator_3
    ATTR_LIST = blockID,@Evaluate(@int(@Value(_list{0}))),blockData,"FME_CONDITIONAL:DEFAULT_VALUE'_FME_NO_OP_'BOOL_OP;OR;COMPOSITE_TEST;<Unused>;TEST _list{1} NOT_ATTRIBUTE_IS_MISSING _FME_BLANK_STRING_'@Evaluate(@int(@Value(_list{1})))'FME_NUM_CONDITIONS2___"
    -> Tester
Tester
    TEST_CLAUSE = TEST blockData NOT_ATTRIBUTE_IS_MISSING ""
    BOOL_OP = OR
    TEST_MODE = Automatic
    TEST_DESCRIPTION = ""
    PASSED -> PointCloudComponentAdder
    FAILED -> PointCloudComponentAdder_2
PointCloudComponentAdder
    COMPONENTS_TO_ADD = blockID,UInt16,@Value(blockID),blockData,UInt8,@Value(blockData),vertical_offset,Int8,@Value(_vertical_offset)
    -> Styled (output)
PointCloudComponentAdder_2
    COMPONENTS_TO_ADD = blockID,UInt16,@Value(blockID),vertical_offset,Int8,@Value(_vertical_offset)
    -> Styled (output)
AttributeCreator_2
    ATTR_LIST = MinecraftBlock,$(MINECRAFTBLOCK)
    -> AttributeSplitter
AttributeSplitter
    ATTR_NAME = MinecraftBlock
    DELIMITER = _
    TRIM_OPTION = Both
    LIST_NAME = _list
    DROP_EMPTY_PARTS = No
    -> AttributeCreator
AttributeCreator
    ATTR_LIST = blockID,@Evaluate(@int(@Value(_list{0}))),blockData,"FME_CONDITIONAL:DEFAULT_VALUE'-1'BOOL_OP;OR;COMPOSITE_TEST;<Unused>;TEST _list{1} NOT_ATTRIBUTE_IS_MISSING _FME_BLANK_STRING_'@Evaluate(@int(@Value(_list{1})))'FME_NUM_CONDITIONS2___"
    -> AttributeRemover
AttributeRemover
    LIST_ATTRS = _list{}
    REMOVE_ATTRS = MinecraftBlock
    -> Styled (output)
Styled (output)

FME custom transformer MinecraftStyler_3
Sets Minecraft blockID and blockData

Parameters:
- MINECRAFTBLOCK = 001_00
- VERTICALOFFSET = 0   # Vertical Offset

Input (input)
    -> ParameterFetcher_3
ParameterFetcher_3
    ATTR_LIST = _vertical_offset {$(VERTICALOFFSET)}
    -> GeometryFilter
GeometryFilter
    BREAK_AGG = No
    GEOM_PORT_NAMES = Pointcloud
    <UNFILTERED> -> AttributeCreator_2
    POINTCLOUD -> PointCloudComponentRemover
PointCloudComponentRemover
    COMPONENTS_TO_REMOVE = blockID,blockData,vertical_offset
    -> ParameterFetcher
ParameterFetcher
    ATTR_LIST = MinecraftBlock {$(MINECRAFTBLOCK)}
    -> AttributeSplitter_2
AttributeSplitter_2
    ATTR_NAME = MinecraftBlock
    DELIMITER = _
    TRIM_OPTION = Both
    LIST_NAME = _list
    DROP_EMPTY_PARTS = No
    -> AttributeCreator_3
AttributeCreator_3
    ATTR_LIST = blockID,@Evaluate(@int(@Value(_list{0}))),blockData,"FME_CONDITIONAL:DEFAULT_VALUE'_FME_NO_OP_'BOOL_OP;OR;COMPOSITE_TEST;<Unused>;TEST _list{1} NOT_ATTRIBUTE_IS_MISSING _FME_BLANK_STRING_'@Evaluate(@int(@Value(_list{1})))'FME_NUM_CONDITIONS2___"
    -> Tester
Tester
    TEST_CLAUSE = TEST blockData NOT_ATTRIBUTE_IS_MISSING ""
    BOOL_OP = OR
    TEST_MODE = Automatic
    TEST_DESCRIPTION = ""
    PASSED -> PointCloudComponentAdder
    FAILED -> PointCloudComponentAdder_2
PointCloudComponentAdder
    COMPONENTS_TO_ADD = blockID,UInt16,@Value(blockID),blockData,UInt8,@Value(blockData),vertical_offset,Int8,@Value(_vertical_offset)
    -> Styled (output)
PointCloudComponentAdder_2
    COMPONENTS_TO_ADD = blockID,UInt16,@Value(blockID),vertical_offset,Int8,@Value(_vertical_offset)
    -> Styled (output)
AttributeCreator_2
    ATTR_LIST = MinecraftBlock,$(MINECRAFTBLOCK)
    -> AttributeSplitter
AttributeSplitter
    ATTR_NAME = MinecraftBlock
    DELIMITER = _
    TRIM_OPTION = Both
    LIST_NAME = _list
    DROP_EMPTY_PARTS = No
    -> AttributeCreator
AttributeCreator
    ATTR_LIST = blockID,@Evaluate(@int(@Value(_list{0}))),blockData,"FME_CONDITIONAL:DEFAULT_VALUE'-1'BOOL_OP;OR;COMPOSITE_TEST;<Unused>;TEST _list{1} NOT_ATTRIBUTE_IS_MISSING _FME_BLANK_STRING_'@Evaluate(@int(@Value(_list{1})))'FME_NUM_CONDITIONS2___"
    -> AttributeRemover
AttributeRemover
    LIST_ATTRS = _list{}
    REMOVE_ATTRS = MinecraftBlock
    -> Styled (output)
Styled (output)

FME custom transformer MinecraftStyler
Sets Minecraft blockID and blockData

Parameters:
- MINECRAFTBLOCK = 001_00
- VERTICALOFFSET = 0   # Vertical Offset

Input (input)
    -> ParameterFetcher_3
ParameterFetcher_3
    ATTR_LIST = _vertical_offset {$(VERTICALOFFSET)}
    -> GeometryFilter
GeometryFilter
    BREAK_AGG = No
    GEOM_PORT_NAMES = Pointcloud
    <UNFILTERED> -> AttributeCreator_2
    POINTCLOUD -> PointCloudComponentRemover
PointCloudComponentRemover
    COMPONENTS_TO_REMOVE = blockID,blockData,vertical_offset
    -> ParameterFetcher
ParameterFetcher
    ATTR_LIST = MinecraftBlock {$(MINECRAFTBLOCK)}
    -> AttributeSplitter_2
AttributeSplitter_2
    ATTR_NAME = MinecraftBlock
    DELIMITER = _
    TRIM_OPTION = Both
    LIST_NAME = _list
    DROP_EMPTY_PARTS = No
    -> AttributeCreator_3
AttributeCreator_3
    ATTR_LIST = blockID,@Evaluate(@int(@Value(_list{0}))),blockData,"FME_CONDITIONAL:DEFAULT_VALUE'_FME_NO_OP_'BOOL_OP;OR;COMPOSITE_TEST;<Unused>;TEST _list{1} NOT_ATTRIBUTE_IS_MISSING _FME_BLANK_STRING_'@Evaluate(@int(@Value(_list{1})))'FME_NUM_CONDITIONS2___"
    -> Tester
Tester
    TEST_CLAUSE = TEST blockData NOT_ATTRIBUTE_IS_MISSING ""
    BOOL_OP = OR
    TEST_MODE = Automatic
    TEST_DESCRIPTION = ""
    PASSED -> PointCloudComponentAdder
    FAILED -> PointCloudComponentAdder_2
PointCloudComponentAdder
    COMPONENTS_TO_ADD = blockID,UInt16,@Value(blockID),blockData,UInt8,@Value(blockData),vertical_offset,Int8,@Value(_vertical_offset)
    -> Styled (output)
PointCloudComponentAdder_2
    COMPONENTS_TO_ADD = blockID,UInt16,@Value(blockID),vertical_offset,Int8,@Value(_vertical_offset)
    -> Styled (output)
AttributeCreator_2
    ATTR_LIST = MinecraftBlock,$(MINECRAFTBLOCK)
    -> AttributeSplitter
AttributeSplitter
    ATTR_NAME = MinecraftBlock
    DELIMITER = _
    TRIM_OPTION = Both
    LIST_NAME = _list
    DROP_EMPTY_PARTS = No
    -> AttributeCreator
AttributeCreator
    ATTR_LIST = blockID,@Evaluate(@int(@Value(_list{0}))),blockData,"FME_CONDITIONAL:DEFAULT_VALUE'-1'BOOL_OP;OR;COMPOSITE_TEST;<Unused>;TEST _list{1} NOT_ATTRIBUTE_IS_MISSING _FME_BLANK_STRING_'@Evaluate(@int(@Value(_list{1})))'FME_NUM_CONDITIONS2___"
    -> AttributeRemover
AttributeRemover
    LIST_ATTRS = _list{}
    REMOVE_ATTRS = MinecraftBlock
    -> Styled (output)
Styled (output)
